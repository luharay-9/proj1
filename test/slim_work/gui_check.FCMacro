import FreeCAD as App,FreeCADGui as Gui
from PySide import QtCore
p='/Users/harrylu/Downloads/proj1/test/'
d=App.openDocument(p+'Shinguard_Slim_Cable_Clearance.FCStd')
Gui.activeDocument().activeView().viewAxonometric()
Gui.activeDocument().activeView().fitAll()
Gui.updateGui()
def finish():
 Gui.activeDocument().activeView().saveImage(p+'Slim_FreeCAD_GUI.png',1400,1000,'White')
 Gui.updateGui()
 print('SLIM_GUI_OPEN_RENDER_SUCCESS',flush=True)
 App.closeDocument(d.Name)
 QtCore.QTimer.singleShot(250,Gui.getMainWindow().close)
QtCore.QTimer.singleShot(2500,finish)
